# -*- coding: utf-8 -*-

# Macro Begin: /home/ensab/rrlOwncloud/RepRapLtd/Engineering/External-Projects/Scantastic/Scanner-Dev/Simulator/col.FCMacro +++++++++++++++++++++++++++++++++++++++++++++++++
import FreeCAD

# Macro End: /home/ensab/rrlOwncloud/RepRapLtd/Engineering/External-Projects/Scantastic/Scanner-Dev/Simulator/col.FCMacro +++++++++++++++++++++++++++++++++++++++++++++++++
